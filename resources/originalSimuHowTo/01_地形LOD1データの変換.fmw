FME workspace 01_地形LOD1データの変換.fmw

Parameters:
- SourceDataset_CITYGML = C:\Users\Administrator\523411_dem_6697_00.gml   # Source CityGML File(s)
- DestDataset_POINTCLOUDXYZ = C:\Users\Administrator   # Destination Point Cloud XYZ Folder

Readers:
- CITYGML_1: CITYGML from $(SourceDataset_CITYGML)

Writers:
- POINTCLOUDXYZ_1: POINTCLOUDXYZ to $(DestDataset_POINTCLOUDXYZ)

Note: 地形LOD1の読み込み
TINRelief (reader CITYGML_1)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38)
    -> PointCloudCombiner
Note: サーフェスを点群に変換
PointCloudCombiner
    ACCUM_ATTRS_NAME = Yes
    EXTRACT_RASTER_NODATA_NAME = No
    SPACING = 1.0
    -> EsriReprojector
Note: 座標系を変換
EsriReprojector
    DEST = ESRIWKT|JGD_2011_Japan_Zone_5|PROJCS["JGD_2011_Japan_Zone_5",GEOGCS["GCS_JGD_2011",DATUM["D_JGD_2011",SPHEROID["GRS_1980",6378137.0,298.257222101]],PRIMEM["Greenwich",0.0],UNIT["Degree",0.0174532925199433]],PROJECTION["Transverse_Mercator"],PARAMETER["False_Easting",0.0],PARAMETER["False_Northing",0.0],PARAMETER["Central_Meridian",134.3333333333333],PARAMETER["Scale_Factor",0.9999],PARAMETER["Latitude_Of_Origin",36.0],UNIT["Meter",1.0]]
    GEOTRANSFORMATION_NAME = <None>
    INTERPOLATION_TYPE_NAME = Nearest Neighbor
    RASTER_CELL_SIZE = Preserve Cells
    RASTER_TOLERANCE = 0.0
    SOURCE = ESRIWKT|GCS_JGD_2011|GEOGCS["GCS_JGD_2011",DATUM["D_JGD_2011",SPHEROID["GRS_1980",6378137.0,298.257222101]],PRIMEM["Greenwich",0.0],UNIT["Degree",0.0174532925199433]]
    REPROJECTED -> TINRelief (writer POINTCLOUDXYZ_1)
Note: XYZ形式で出力
TINRelief (writer POINTCLOUDXYZ_1)
