FME workspace 02_建築物LOD1データの変換.fmw

Parameters:
- DestDataset_SHAPEFILE = C:\Users\Administrator   # Destination Esri Shapefile Folder
- SourceDataset_CITYGML = C:\Users\Administrator\52341127_bldg_6697.gml   # Source CityGML File(s)

Readers:
- CITYGML_2: CITYGML from $(SourceDataset_CITYGML)

Writers:
- SHAPEFILE_1: SHAPEFILE to $(DestDataset_SHAPEFILE) in JGD2011-05_FME

Note: 建築物LOD1の読み込み
Building (reader CITYGML_2)
    attributes: citygml_target_uri xml_buffer, citygml_feature_role xml_buffer, citygml_feature_role_attr_name xml_buffer, citygml_feature_role_attr_val xml_buffer, gml_description xml_buffer, gml_name xml_buffer, citygml_creationDate xml_date, citygml_terminationDate xml_date, externalReference{}.externalObject.name xml_xml, externalReference{}.externalObject.uri xml_xml, externalReference{}.informationSystem xml_xml, citygml_generalizes_to{}.xlink_href xml_buffer, citygml_relative_to_terrain xml_char(33), citygml_relative_to_water xml_char(38), citygml_class xml_buffer, citygml_class_codeSpace xml_buffer, citygml_function{} xml_buffer, citygml_function{}.codeSpace xml_buffer, citygml_usage{} xml_buffer, citygml_usage{}.codeSpace xml_buffer, citygml_year_of_construction xml_buffer, citygml_year_of_demolition xml_buffer, citygml_roof_type xml_buffer, citygml_roof_type_codeSpace xml_buffer, citygml_measured_height xml_real64, citygml_measured_height_units xml_buffer, citygml_storeys_above_ground xml_uint64, citygml_storeys_below_ground xml_uint64, citygml_storey_heights_above_ground xml_buffer, citygml_storey_heights_above_ground_units xml_buffer,
      citygml_storey_heights_below_ground xml_buffer, citygml_storey_heights_below_ground_units xml_buffer, citygml_outer_building_installation{}.xlink_href xml_buffer, citygml_interior_building_installation{}.xlink_href xml_buffer, citygml_bounded_by{}.xlink_href xml_buffer, citygml_level_of_detail{} xml_buffer, citygml_interior_room{}.xlink_href xml_buffer, citygml_consists_of_building_part{}.xlink_href xml_buffer, citygml_address{}.xlink_href xml_buffer, uro_bldg_facility_attribute{} xml_xml, uro_bldg_facility_id_attribute{}.uro_river_facility_id_attribute_uro_id xml_buffer, uro_bldg_facility_id_attribute{}.uro_river_facility_id_attribute_uro_part_id xml_buffer, uro_bldg_facility_id_attribute{}.uro_river_facility_id_attribute_uro_branch_id xml_buffer, uro_bldg_facility_id_attribute{}.uro_river_facility_id_attribute_uro_prefecture{} xml_buffer, uro_bldg_facility_id_attribute{}.uro_river_facility_id_attribute_uro_prefecture{}.codeSpace xml_buffer, uro_bldg_facility_id_attribute{}.uro_river_facility_id_attribute_uro_city{} xml_buffer, uro_bldg_facility_id_attribute{}.uro_river_facility_id_attribute_uro_city{}.codeSpace xml_buffer, uro_bldg_facility_id_attribute{}.uro_river_facility_id_attribute_uro_route xml_buffer, uro_bldg_facility_id_attribute{}.uro_river_facility_id_attribute_uro_start_post xml_buffer, uro_bldg_facility_id_attribute{}.uro_river_facility_id_attribute_uro_end_post xml_buffer, uro_bldg_facility_id_attribute{}.uro_river_facility_id_attribute_uro_start_lat xml_real64, uro_bldg_facility_id_attribute{}.uro_river_facility_id_attribute_uro_start_long xml_real64, uro_bldg_facility_id_attribute{}.uro_river_facility_id_attribute_uro_alternative_name{} xml_buffer, uro_bldg_facility_id_attribute{}.uro_river_facility_id_attribute_uro_river_code xml_buffer, uro_bldg_facility_id_attribute{}.uro_river_facility_id_attribute_uro_river_code_codeSpace xml_buffer, uro_bldg_facility_id_attribute{}.uro_river_facility_id_attribute_uro_river_name xml_buffer, uro_bldg_facility_id_attribute{}.uro_river_facility_id_attribute_uro_side_type xml_buffer, uro_bldg_facility_id_attribute{}.uro_river_facility_id_attribute_uro_side_type_codeSpace xml_buffer, uro_bldg_facility_id_attribute{}.uro_river_facility_id_attribute_uro_left_post xml_real64, uro_bldg_facility_id_attribute{}.uro_river_facility_id_attribute_uro_left_post_units xml_buffer,
      uro_bldg_facility_id_attribute{}.uro_river_facility_id_attribute_uro_left_distance xml_real64, uro_bldg_facility_id_attribute{}.uro_river_facility_id_attribute_uro_left_distance_units xml_buffer, uro_bldg_facility_id_attribute{}.uro_river_facility_id_attribute_uro_right_post xml_real64, uro_bldg_facility_id_attribute{}.uro_river_facility_id_attribute_uro_right_post_units xml_buffer, uro_bldg_facility_id_attribute{}.uro_river_facility_id_attribute_uro_right_distance xml_real64, uro_bldg_facility_id_attribute{}.uro_river_facility_id_attribute_uro_right_distance_units xml_buffer, uro_bldg_facility_id_attribute{}.uro_river_facility_id_attribute_uro_left_start_post xml_real64, uro_bldg_facility_id_attribute{}.uro_river_facility_id_attribute_uro_left_start_post_units xml_buffer, uro_bldg_facility_id_attribute{}.uro_river_facility_id_attribute_uro_left_start_distance xml_real64, uro_bldg_facility_id_attribute{}.uro_river_facility_id_attribute_uro_left_start_distance_units xml_buffer, uro_bldg_facility_id_attribute{}.uro_river_facility_id_attribute_uro_left_end_post xml_real64, uro_bldg_facility_id_attribute{}.uro_river_facility_id_attribute_uro_left_end_post_units xml_buffer, uro_bldg_facility_id_attribute{}.uro_river_facility_id_attribute_uro_lef_end_distance xml_real64, uro_bldg_facility_id_attribute{}.uro_river_facility_id_attribute_uro_lef_end_distance_units xml_buffer, uro_bldg_facility_id_attribute{}.uro_river_facility_id_attribute_uro_right_start_post xml_real64, uro_bldg_facility_id_attribute{}.uro_river_facility_id_attribute_uro_right_start_post_units xml_buffer, uro_bldg_facility_id_attribute{}.uro_river_facility_id_attribute_uro_right_start_distance xml_real64, uro_bldg_facility_id_attribute{}.uro_river_facility_id_attribute_uro_right_start_distance_units xml_buffer, uro_bldg_facility_id_attribute{}.uro_river_facility_id_attribute_uro_right_end_post xml_real64, uro_bldg_facility_id_attribute{}.uro_river_facility_id_attribute_uro_right_end_post_units xml_buffer, uro_bldg_facility_id_attribute{}.uro_river_facility_id_attribute_uro_right_end_distance xml_real64, uro_bldg_facility_id_attribute{}.uro_river_facility_id_attribute_uro_right_end_distance_units xml_buffer, uro_bldg_facility_id_attribute{}.uro_facility_id_attribute_uro_id xml_buffer, uro_bldg_facility_id_attribute{}.uro_facility_id_attribute_uro_part_id xml_buffer, uro_bldg_facility_id_attribute{}.uro_facility_id_attribute_uro_branch_id xml_buffer, uro_bldg_facility_id_attribute{}.uro_facility_id_attribute_uro_prefecture{} xml_buffer, uro_bldg_facility_id_attribute{}.uro_facility_id_attribute_uro_prefecture{}.codeSpace xml_buffer, uro_bldg_facility_id_attribute{}.uro_facility_id_attribute_uro_city{} xml_buffer, uro_bldg_facility_id_attribute{}.uro_facility_id_attribute_uro_city{}.codeSpace xml_buffer, uro_bldg_facility_id_attribute{}.uro_facility_id_attribute_uro_route xml_buffer,
      uro_bldg_facility_id_attribute{}.uro_facility_id_attribute_uro_start_post xml_buffer, uro_bldg_facility_id_attribute{}.uro_facility_id_attribute_uro_end_post xml_buffer, uro_bldg_facility_id_attribute{}.uro_facility_id_attribute_uro_start_lat xml_real64, uro_bldg_facility_id_attribute{}.uro_facility_id_attribute_uro_start_long xml_real64, uro_bldg_facility_id_attribute{}.uro_facility_id_attribute_uro_alternative_name{} xml_buffer, uro_bldg_facility_type_attribute{}.uro_facility_type_attribute_uro_class xml_buffer, uro_bldg_facility_type_attribute{}.uro_facility_type_attribute_uro_class_codeSpace xml_buffer, uro_bldg_facility_type_attribute{}.uro_facility_type_attribute_uro_function{} xml_buffer, uro_bldg_facility_type_attribute{}.uro_facility_type_attribute_uro_function{}.codeSpace xml_buffer, uro_building_data_quality_attribute{}.uro_building_data_quality_attribute_uro_src_scale{} xml_buffer, uro_building_data_quality_attribute{}.uro_building_data_quality_attribute_uro_src_scale{}.codeSpace xml_buffer, uro_building_data_quality_attribute{}.uro_building_data_quality_attribute_uro_geometry_src_desc{} xml_buffer, uro_building_data_quality_attribute{}.uro_building_data_quality_attribute_uro_geometry_src_desc{}.codeSpace xml_buffer, uro_building_data_quality_attribute{}.uro_building_data_quality_attribute_uro_thematic_src_desc{} xml_buffer, uro_building_data_quality_attribute{}.uro_building_data_quality_attribute_uro_thematic_src_desc{}.codeSpace xml_buffer, uro_building_data_quality_attribute{}.uro_building_data_quality_attribute_uro_appearance_src_desc{} xml_buffer, uro_building_data_quality_attribute{}.uro_building_data_quality_attribute_uro_appearance_src_desc{}.codeSpace xml_buffer, uro_building_data_quality_attribute{}.uro_building_data_quality_attribute_uro_lod1_height_type xml_buffer, uro_building_data_quality_attribute{}.uro_building_data_quality_attribute_uro_lod1_height_type_codeSpace xml_buffer, uro_building_data_quality_attribute{}.uro_building_data_quality_attribute_uro_lod_type{} xml_char(3), uro_building_detail_attribute{}.uro_building_detail_attribute_uro_serial_number_of_building_certification xml_buffer, uro_building_detail_attribute{}.uro_building_detail_attribute_uro_site_area xml_real64, uro_building_detail_attribute{}.uro_building_detail_attribute_uro_site_area_units xml_buffer, uro_building_detail_attribute{}.uro_building_detail_attribute_uro_total_floor_area xml_real64, uro_building_detail_attribute{}.uro_building_detail_attribute_uro_total_floor_area_units xml_buffer, uro_building_detail_attribute{}.uro_building_detail_attribute_uro_building_footprint_area xml_real64, uro_building_detail_attribute{}.uro_building_detail_attribute_uro_building_footprint_area_units xml_buffer, uro_building_detail_attribute{}.uro_building_detail_attribute_uro_building_roof_edge_area xml_real64, uro_building_detail_attribute{}.uro_building_detail_attribute_uro_building_roof_edge_area_units xml_buffer, uro_building_detail_attribute{}.uro_building_detail_attribute_uro_development_area xml_real64,
      uro_building_detail_attribute{}.uro_building_detail_attribute_uro_development_area_units xml_buffer, uro_building_detail_attribute{}.uro_building_detail_attribute_uro_building_structure_type xml_buffer, uro_building_detail_attribute{}.uro_building_detail_attribute_uro_building_structure_type_codeSpace xml_buffer, uro_building_detail_attribute{}.uro_building_detail_attribute_uro_building_structure_org_type xml_buffer, uro_building_detail_attribute{}.uro_building_detail_attribute_uro_building_structure_org_type_codeSpace xml_buffer, uro_building_detail_attribute{}.uro_building_detail_attribute_uro_fireproof_structure_type xml_buffer, uro_building_detail_attribute{}.uro_building_detail_attribute_uro_fireproof_structure_type_codeSpace xml_buffer, uro_building_detail_attribute{}.uro_building_detail_attribute_uro_implementing_body xml_buffer, uro_building_detail_attribute{}.uro_building_detail_attribute_uro_urban_plan_type xml_buffer, uro_building_detail_attribute{}.uro_building_detail_attribute_uro_urban_plan_type_codeSpace xml_buffer, uro_building_detail_attribute{}.uro_building_detail_attribute_uro_area_classification_type xml_buffer, uro_building_detail_attribute{}.uro_building_detail_attribute_uro_area_classification_type_codeSpace xml_buffer, uro_building_detail_attribute{}.uro_building_detail_attribute_uro_districts_and_zones_type{} xml_buffer, uro_building_detail_attribute{}.uro_building_detail_attribute_uro_districts_and_zones_type{}.codeSpace xml_buffer, uro_building_detail_attribute{}.uro_building_detail_attribute_uro_land_use_type xml_buffer, uro_building_detail_attribute{}.uro_building_detail_attribute_uro_land_use_type_codeSpace xml_buffer, uro_building_detail_attribute{}.uro_building_detail_attribute_uro_reference xml_buffer, uro_building_detail_attribute{}.uro_building_detail_attribute_uro_major_usage xml_buffer, uro_building_detail_attribute{}.uro_building_detail_attribute_uro_major_usage_codeSpace xml_buffer, uro_building_detail_attribute{}.uro_building_detail_attribute_uro_major_usage2 xml_buffer, uro_building_detail_attribute{}.uro_building_detail_attribute_uro_major_usage2_codeSpace xml_buffer, uro_building_detail_attribute{}.uro_building_detail_attribute_uro_org_usage xml_buffer, uro_building_detail_attribute{}.uro_building_detail_attribute_uro_org_usage_codeSpace xml_buffer, uro_building_detail_attribute{}.uro_building_detail_attribute_uro_org_usage2 xml_buffer, uro_building_detail_attribute{}.uro_building_detail_attribute_uro_org_usage2_codeSpace xml_buffer, uro_building_detail_attribute{}.uro_building_detail_attribute_uro_detailed_usage xml_buffer, uro_building_detail_attribute{}.uro_building_detail_attribute_uro_detailed_usage_codeSpace xml_buffer, uro_building_detail_attribute{}.uro_building_detail_attribute_uro_detailed_usage2 xml_buffer, uro_building_detail_attribute{}.uro_building_detail_attribute_uro_detailed_usage2_codeSpace xml_buffer, uro_building_detail_attribute{}.uro_building_detail_attribute_uro_detailed_usage3 xml_buffer,
      uro_building_detail_attribute{}.uro_building_detail_attribute_uro_detailed_usage3_codeSpace xml_buffer, uro_building_detail_attribute{}.uro_building_detail_attribute_uro_ground_floor_usage xml_buffer, uro_building_detail_attribute{}.uro_building_detail_attribute_uro_ground_floor_usage_codeSpace xml_buffer, uro_building_detail_attribute{}.uro_building_detail_attribute_uro_second_floor_usage xml_buffer, uro_building_detail_attribute{}.uro_building_detail_attribute_uro_second_floor_usage_codeSpace xml_buffer, uro_building_detail_attribute{}.uro_building_detail_attribute_uro_third_floor_usage xml_buffer, uro_building_detail_attribute{}.uro_building_detail_attribute_uro_third_floor_usage_codeSpace xml_buffer, uro_building_detail_attribute{}.uro_building_detail_attribute_uro_basement_usage xml_buffer, uro_building_detail_attribute{}.uro_building_detail_attribute_uro_basement_usage_codeSpace xml_buffer, uro_building_detail_attribute{}.uro_building_detail_attribute_uro_basement_first_usage xml_buffer, uro_building_detail_attribute{}.uro_building_detail_attribute_uro_basement_first_usage_codeSpace xml_buffer, uro_building_detail_attribute{}.uro_building_detail_attribute_uro_basement_second_usage xml_buffer, uro_building_detail_attribute{}.uro_building_detail_attribute_uro_basement_second_usage_codeSpace xml_buffer, uro_building_detail_attribute{}.uro_building_detail_attribute_uro_vacancy xml_buffer, uro_building_detail_attribute{}.uro_building_detail_attribute_uro_vacancy_codeSpace xml_buffer, uro_building_detail_attribute{}.uro_building_detail_attribute_uro_building_coverage_rate xml_real64, uro_building_detail_attribute{}.uro_building_detail_attribute_uro_floor_area_rate xml_real64, uro_building_detail_attribute{}.uro_building_detail_attribute_uro_specified_building_coverage_rate xml_real64, uro_building_detail_attribute{}.uro_building_detail_attribute_uro_specified_floor_area_rate xml_real64, uro_building_detail_attribute{}.uro_building_detail_attribute_uro_standard_floor_area_rate xml_real64, uro_building_detail_attribute{}.uro_building_detail_attribute_uro_building_height xml_real64, uro_building_detail_attribute{}.uro_building_detail_attribute_uro_building_height_units xml_buffer, uro_building_detail_attribute{}.uro_building_detail_attribute_uro_eave_height xml_real64, uro_building_detail_attribute{}.uro_building_detail_attribute_uro_eave_height_units xml_buffer, uro_building_detail_attribute{}.uro_building_detail_attribute_uro_note xml_buffer, uro_building_detail_attribute{}.uro_building_detail_attribute_uro_survey_year xml_buffer, uro_building_disaster_risk_attribute{}.uro_building_high_tide_risk_attribute_uro_description xml_buffer, uro_building_disaster_risk_attribute{}.uro_building_high_tide_risk_attribute_uro_description_codeSpace xml_buffer, uro_building_disaster_risk_attribute{}.uro_building_high_tide_risk_attribute_uro_rank xml_buffer, uro_building_disaster_risk_attribute{}.uro_building_high_tide_risk_attribute_uro_rank_codeSpace xml_buffer,
      uro_building_disaster_risk_attribute{}.uro_building_high_tide_risk_attribute_uro_rank_org xml_buffer, uro_building_disaster_risk_attribute{}.uro_building_high_tide_risk_attribute_uro_rank_org_codeSpace xml_buffer, uro_building_disaster_risk_attribute{}.uro_building_high_tide_risk_attribute_uro_depth xml_real64, uro_building_disaster_risk_attribute{}.uro_building_high_tide_risk_attribute_uro_depth_units xml_buffer, uro_building_disaster_risk_attribute{}.uro_building_inland_flooding_risk_attribute_uro_description xml_buffer, uro_building_disaster_risk_attribute{}.uro_building_inland_flooding_risk_attribute_uro_description_codeSpace xml_buffer, uro_building_disaster_risk_attribute{}.uro_building_inland_flooding_risk_attribute_uro_rank xml_buffer, uro_building_disaster_risk_attribute{}.uro_building_inland_flooding_risk_attribute_uro_rank_codeSpace xml_buffer, uro_building_disaster_risk_attribute{}.uro_building_inland_flooding_risk_attribute_uro_rank_org xml_buffer, uro_building_disaster_risk_attribute{}.uro_building_inland_flooding_risk_attribute_uro_rank_org_codeSpace xml_buffer, uro_building_disaster_risk_attribute{}.uro_building_inland_flooding_risk_attribute_uro_depth xml_real64, uro_building_disaster_risk_attribute{}.uro_building_inland_flooding_risk_attribute_uro_depth_units xml_buffer, uro_building_disaster_risk_attribute{}.uro_building_land_slide_risk_attribute_uro_description xml_buffer, uro_building_disaster_risk_attribute{}.uro_building_land_slide_risk_attribute_uro_description_codeSpace xml_buffer, uro_building_disaster_risk_attribute{}.uro_building_land_slide_risk_attribute_uro_area_type xml_buffer, uro_building_disaster_risk_attribute{}.uro_building_land_slide_risk_attribute_uro_area_type_codeSpace xml_buffer, uro_building_disaster_risk_attribute{}.uro_building_river_flooding_risk_attribute_uro_description xml_buffer, uro_building_disaster_risk_attribute{}.uro_building_river_flooding_risk_attribute_uro_description_codeSpace xml_buffer, uro_building_disaster_risk_attribute{}.uro_building_river_flooding_risk_attribute_uro_rank xml_buffer, uro_building_disaster_risk_attribute{}.uro_building_river_flooding_risk_attribute_uro_rank_codeSpace xml_buffer, uro_building_disaster_risk_attribute{}.uro_building_river_flooding_risk_attribute_uro_rank_org xml_buffer, uro_building_disaster_risk_attribute{}.uro_building_river_flooding_risk_attribute_uro_rank_org_codeSpace xml_buffer, uro_building_disaster_risk_attribute{}.uro_building_river_flooding_risk_attribute_uro_depth xml_real64, uro_building_disaster_risk_attribute{}.uro_building_river_flooding_risk_attribute_uro_depth_units xml_buffer, uro_building_disaster_risk_attribute{}.uro_building_river_flooding_risk_attribute_uro_admin_type xml_buffer, uro_building_disaster_risk_attribute{}.uro_building_river_flooding_risk_attribute_uro_admin_type_codeSpace xml_buffer, uro_building_disaster_risk_attribute{}.uro_building_river_flooding_risk_attribute_uro_scale xml_buffer, uro_building_disaster_risk_attribute{}.uro_building_river_flooding_risk_attribute_uro_scale_codeSpace xml_buffer, uro_building_disaster_risk_attribute{}.uro_building_river_flooding_risk_attribute_uro_duration xml_real64, uro_building_disaster_risk_attribute{}.uro_building_river_flooding_risk_attribute_uro_duration_units xml_buffer,
      uro_building_disaster_risk_attribute{}.uro_building_tsunami_risk_attribute_uro_description xml_buffer, uro_building_disaster_risk_attribute{}.uro_building_tsunami_risk_attribute_uro_description_codeSpace xml_buffer, uro_building_disaster_risk_attribute{}.uro_building_tsunami_risk_attribute_uro_rank xml_buffer, uro_building_disaster_risk_attribute{}.uro_building_tsunami_risk_attribute_uro_rank_codeSpace xml_buffer, uro_building_disaster_risk_attribute{}.uro_building_tsunami_risk_attribute_uro_rank_org xml_buffer, uro_building_disaster_risk_attribute{}.uro_building_tsunami_risk_attribute_uro_rank_org_codeSpace xml_buffer, uro_building_disaster_risk_attribute{}.uro_building_tsunami_risk_attribute_uro_depth xml_real64, uro_building_disaster_risk_attribute{}.uro_building_tsunami_risk_attribute_uro_depth_units xml_buffer, uro_building_idattribute{}.uro_building_idattribute_uro_building_id xml_buffer, uro_building_idattribute{}.uro_building_idattribute_uro_branch_id xml_int64, uro_building_idattribute{}.uro_building_idattribute_uro_part_id xml_int64, uro_building_idattribute{}.uro_building_idattribute_uro_prefecture xml_buffer, uro_building_idattribute{}.uro_building_idattribute_uro_prefecture_codeSpace xml_buffer, uro_building_idattribute{}.uro_building_idattribute_uro_city xml_buffer, uro_building_idattribute{}.uro_building_idattribute_uro_city_codeSpace xml_buffer, uro_ifc_building_attribute{} xml_xml, uro_indoor_building_attribute{}.uro_indoor_facility_attribute_uro_source xml_buffer, uro_indoor_building_attribute{}.uro_indoor_facility_attribute_uro_source_codeSpace xml_buffer, uro_indoor_building_attribute{}.uro_indoor_facility_attribute_uro_weekday_hours xml_buffer, uro_indoor_building_attribute{}.uro_indoor_facility_attribute_uro_weekend_hours xml_buffer, uro_indoor_building_attribute{}.uro_indoor_facility_attribute_uro_phone xml_buffer, uro_indoor_building_attribute{}.uro_indoor_facility_attribute_uro_website xml_buffer, uro_indoor_building_attribute{}.uro_indoor_furnishing_attribute_uro_source xml_buffer, uro_indoor_building_attribute{}.uro_indoor_furnishing_attribute_uro_source_codeSpace xml_buffer, uro_indoor_building_attribute{}.uro_indoor_furnishing_attribute_uro_floor_id xml_buffer, uro_indoor_building_attribute{}.uro_indoor_public_tag_attribute_uro_source xml_buffer, uro_indoor_building_attribute{}.uro_indoor_public_tag_attribute_uro_source_codeSpace xml_buffer, uro_indoor_building_attribute{}.uro_indoor_public_tag_attribute_uro_ucode xml_buffer, uro_indoor_building_attribute{}.uro_indoor_space_attribute_uro_source xml_buffer, uro_indoor_building_attribute{}.uro_indoor_space_attribute_uro_source_codeSpace xml_buffer,
      uro_indoor_building_attribute{}.uro_indoor_space_attribute_uro_floor_id xml_buffer, uro_indoor_building_attribute{}.uro_indoor_space_attribute_uro_is_restricted xml_boolean, uro_indoor_building_attribute{}.uro_indoor_space_attribute_uro_suite xml_buffer, uro_indoor_building_attribute{}.uro_indoor_space_attribute_uro_is_public xml_boolean, uro_indoor_building_attribute{}.uro_indoor_space_attribute_uro_toll_type xml_buffer, uro_indoor_building_attribute{}.uro_indoor_space_attribute_uro_toll_type_codeSpace xml_buffer, uro_indoor_building_attribute{}.uro_indoor_storey_attribute_uro_source xml_buffer, uro_indoor_building_attribute{}.uro_indoor_storey_attribute_uro_source_codeSpace xml_buffer, uro_indoor_building_attribute{}.uro_indoor_storey_attribute_uro_category xml_boolean, uro_indoor_building_attribute{}.uro_indoor_storey_attribute_uro_ordinal xml_real64, uro_indoor_building_attribute{}.uro_indoor_tacatile_tile_attribute_uro_source xml_buffer, uro_indoor_building_attribute{}.uro_indoor_tacatile_tile_attribute_uro_source_codeSpace xml_buffer, uro_indoor_building_attribute{}.uro_indoor_tacatile_tile_attribute_uro_start_node xml_buffer, uro_indoor_building_attribute{}.uro_indoor_tacatile_tile_attribute_uro_end_node xml_buffer, uro_indoor_building_attribute{}.uro_indoor_tacatile_tile_attribute_uro_category xml_buffer, uro_indoor_building_attribute{}.uro_indoor_tacatile_tile_attribute_uro_category_codeSpace xml_buffer, uro_indoor_building_attribute{}.uro_indoor_tacatile_tile_attribute_uro_roof xml_buffer, uro_indoor_building_attribute{}.uro_indoor_tacatile_tile_attribute_uro_floor_id xml_buffer, uro_indoor_building_attribute{}.uro_indoor_user_defined_attribute_uro_source xml_buffer, uro_indoor_building_attribute{}.uro_indoor_user_defined_attribute_uro_source_codeSpace xml_buffer, uro_indoor_building_attribute{}.uro_indoor_user_defined_attribute_uro_name xml_buffer, uro_indoor_building_attribute{}.uro_indoor_user_defined_attribute_uro_nominal_value_uro_user_defined_value_uro_string_value xml_buffer, uro_indoor_building_attribute{}.uro_indoor_user_defined_attribute_uro_nominal_value_uro_user_defined_value_uro_int_value xml_int64, uro_indoor_building_attribute{}.uro_indoor_user_defined_attribute_uro_nominal_value_uro_user_defined_value_uro_double_value xml_real64, uro_indoor_building_attribute{}.uro_indoor_user_defined_attribute_uro_nominal_value_uro_user_defined_value_uro_code_value xml_buffer, uro_indoor_building_attribute{}.uro_indoor_user_defined_attribute_uro_nominal_value_uro_user_defined_value_uro_code_value_codeSpace xml_buffer, uro_indoor_building_attribute{}.uro_indoor_user_defined_attribute_uro_nominal_value_uro_user_defined_value_uro_date_value xml_date, uro_indoor_building_attribute{}.uro_indoor_user_defined_attribute_uro_nominal_value_uro_user_defined_value_uro_uri_value xml_buffer, uro_indoor_building_attribute{}.uro_indoor_user_defined_attribute_uro_nominal_value_uro_user_defined_value_uro_measured_value xml_real64, uro_indoor_building_attribute{}.uro_indoor_user_defined_attribute_uro_nominal_value_uro_user_defined_value_uro_measured_value_units xml_buffer,
      uro_indoor_building_attribute{}.uro_indoor_user_defined_attribute_uro_description xml_buffer, uro_indoor_building_attribute{}.uro_indoor_user_defined_attribute_uro_unit xml_buffer, uro_indoor_building_attribute{}.uro_indoor_zone_attribute_uro_source xml_buffer, uro_indoor_building_attribute{}.uro_indoor_zone_attribute_uro_source_codeSpace xml_buffer, uro_indoor_building_attribute{}.uro_indoor_zone_attribute_uro_floor_id xml_buffer, uro_key_value_pair_attribute{}.uro_key_value_pair_attribute_uro_key xml_buffer, uro_key_value_pair_attribute{}.uro_key_value_pair_attribute_uro_key_codeSpace xml_buffer, uro_key_value_pair_attribute{}.uro_key_value_pair_attribute_uro_code_value xml_buffer, uro_key_value_pair_attribute{}.uro_key_value_pair_attribute_uro_code_value_codeSpace xml_buffer, uro_key_value_pair_attribute{}.uro_key_value_pair_attribute_uro_string_value xml_buffer, uro_key_value_pair_attribute{}.uro_key_value_pair_attribute_uro_int_value xml_int64, uro_key_value_pair_attribute{}.uro_key_value_pair_attribute_uro_double_value xml_real64, uro_key_value_pair_attribute{}.uro_key_value_pair_attribute_uro_measured_value xml_real64, uro_key_value_pair_attribute{}.uro_key_value_pair_attribute_uro_measured_value_units xml_buffer, uro_key_value_pair_attribute{}.uro_key_value_pair_attribute_uro_date_value xml_date, uro_key_value_pair_attribute{}.uro_key_value_pair_attribute_uro_uri_value xml_buffer, uro_large_customer_facility_attribute{}.uro_large_customer_facility_attribute_uro_class xml_buffer, uro_large_customer_facility_attribute{}.uro_large_customer_facility_attribute_uro_class_codeSpace xml_buffer, uro_large_customer_facility_attribute{}.uro_large_customer_facility_attribute_uro_name xml_buffer, uro_large_customer_facility_attribute{}.uro_large_customer_facility_attribute_uro_capacity xml_int64, uro_large_customer_facility_attribute{}.uro_large_customer_facility_attribute_uro_owner xml_buffer, uro_large_customer_facility_attribute{}.uro_large_customer_facility_attribute_uro_total_floor_area xml_real64, uro_large_customer_facility_attribute{}.uro_large_customer_facility_attribute_uro_total_floor_area_units xml_buffer, uro_large_customer_facility_attribute{}.uro_large_customer_facility_attribute_uro_total_store_floor_area xml_real64, uro_large_customer_facility_attribute{}.uro_large_customer_facility_attribute_uro_total_store_floor_area_units xml_buffer, uro_large_customer_facility_attribute{}.uro_large_customer_facility_attribute_uro_inaugural_date xml_date, uro_large_customer_facility_attribute{}.uro_large_customer_facility_attribute_uro_year_opened xml_buffer, uro_large_customer_facility_attribute{}.uro_large_customer_facility_attribute_uro_year_closed xml_buffer, uro_large_customer_facility_attribute{}.uro_large_customer_facility_attribute_uro_key_tenants xml_buffer, uro_large_customer_facility_attribute{}.uro_large_customer_facility_attribute_uro_availability xml_boolean,
      uro_large_customer_facility_attribute{}.uro_large_customer_facility_attribute_uro_urban_plan_type xml_buffer, uro_large_customer_facility_attribute{}.uro_large_customer_facility_attribute_uro_urban_plan_type_codeSpace xml_buffer, uro_large_customer_facility_attribute{}.uro_large_customer_facility_attribute_uro_area_classification_type xml_buffer, uro_large_customer_facility_attribute{}.uro_large_customer_facility_attribute_uro_area_classification_type_codeSpace xml_buffer, uro_large_customer_facility_attribute{}.uro_large_customer_facility_attribute_uro_districts_and_zones_type{} xml_buffer, uro_large_customer_facility_attribute{}.uro_large_customer_facility_attribute_uro_districts_and_zones_type{}.codeSpace xml_buffer, uro_large_customer_facility_attribute{}.uro_large_customer_facility_attribute_uro_land_use_type xml_buffer, uro_large_customer_facility_attribute{}.uro_large_customer_facility_attribute_uro_land_use_type_codeSpace xml_buffer, uro_large_customer_facility_attribute{}.uro_large_customer_facility_attribute_uro_reference xml_buffer, uro_large_customer_facility_attribute{}.uro_large_customer_facility_attribute_uro_note xml_buffer, uro_large_customer_facility_attribute{}.uro_large_customer_facility_attribute_uro_survey_year xml_buffer
    -> AttributeKeeper
Note: 必要な属性だけ抽出
AttributeKeeper
    CREATE_BULK_MODE_FEATURES = NO
    KEEP_ATTRS = citygml_measured_height
    KEEP_LIST = uro_building_detail_attribute{}.uro_building_detail_attribute_uro_building_structure_type uro_key_value_pair_attribute{}.uro_key_value_pair_attribute_uro_code_value uro_key_value_pair_attribute{}.uro_key_value_pair_attribute_uro_key
    -> AttributeManager
Note: 属性名の変更
AttributeManager
    ATTR_TABLE:
      SET_TO kouzou = @Value(uro_building_detail_attribute{0}.uro_building_detail_attribute_uro_building_structure_type)
      SET_TO nendai = FME_CONDITIONAL:DEFAULT_VALUE'_FME_NO_OP_'BOOL_OP;OR;COMPOSITE_TEST;1;TEST @Value(uro_key_value_pair_attribute{0}.uro_key_value_pair_attribute_uro_key) = 100'@Value(uro_key_value_pair_attribute{0}.uro_key_value_pair_attribute_uro_code_value)'BOOL_OP;OR;COMPOSITE_TEST;1;TEST @Value(uro_key_value_pair_attribute{1}.uro_key_value_pair_attribute_uro_key) = 100'@Value(uro_key_value_pair_attribute{1}.uro_key_value_pair_attribute_uro_code_value)'FME_NUM_CONDITIONS3___
    USER_EXPOSED_ATTRIBUTES = toukinobeyukamenseki
    -> 2DForcer
Note: 2Dポリゴンに変換
2DForcer
    2D -> Building (writer SHAPEFILE_1)
Note: 建物SHPの出力
Building (writer SHAPEFILE_1)
    attributes: height float, kouzou number(254,10), nendai number(254,10)
